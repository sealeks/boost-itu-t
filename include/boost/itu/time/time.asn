-- ASN module extracted from ITU-T X.680 (11/2008)

DefinedTime {joint-iso-itu-t asn1(1) specification(0) modules(0) defined-types-module(3011)}
DEFINITIONS AUTOMATIC TAGS ::= BEGIN
EXPORTS ALL; 
--32.2 Encoding subtypes with the "Basic=Date" property setting

-- 32.2.1 The CENTURY-ENCODING type is:
CENTURY-ENCODING  ::= SEQUENCE {
 as-number INTEGER(0..99) -- 7 bits -- }


-- 32.2.2 The ANY-CENTURY-ENCODING type is:
ANY-CENTURY-ENCODING  ::= SEQUENCE {
 as-number INTEGER(MIN..MAX)}

-- 32.2.3 The YEAR-ENCODING type is:
YEAR-ENCODING ::= CHOICE { -- 2 bits for choice determinant
immediate INTEGER (2005..2020), -- 4 bits
near-future INTEGER (2021..2276), -- 8 bits
near-past INTEGER (1749..2004), -- 8 bits
remainder INTEGER (MIN..1748 | 2277..MAX)}

-- 32.2.4 The ANY-YEAR-ENCODING type is:
ANY-YEAR-ENCODING  ::= SEQUENCE {
as-number INTEGER(MIN..MAX) }

-- 32.2.5 The YEAR-MONTH-ENCODING type is:
YEAR-MONTH-ENCODING ::= SEQUENCE {
year YEAR-ENCODING,
month INTEGER (1..12) -- 4 bits -- }

-- 32.2.6 The ANY-YEAR-MONTH-ENCODING type is:
ANY-YEAR-MONTH-ENCODING ::= SEQUENCE {
year ANY-YEAR-ENCODING,
month INTEGER (1..12) }

-- 32.2.7 The DATE-ENCODING type is:
DATE-ENCODING ::= SEQUENCE {
year YEAR-ENCODING,
month INTEGER (1..12), -- 4 bits
day INTEGER (1..31) -- 5 bits -- }

-- 32.2.8 The ANY-DATE-ENCODING type is:
ANY-DATE-ENCODING ::= SEQUENCE {
year ANY-YEAR-ENCODING,
month INTEGER (1..12),
day INTEGER (1..31)}

-- 32.2.9 The YEAR-DAY-ENCODING type is:
YEAR-DAY-ENCODING ::= SEQUENCE {
year YEAR-ENCODING,
day INTEGER (1..366)}

-- 32.2.10 The ANY-YEAR-DAY-ENCODING type is:
ANY-YEAR-DAY-ENCODING ::= SEQUENCE {
year ANY-YEAR-ENCODING,
day INTEGER (1..366)}

-- 32.2.11 The YEAR-WEEK-ENCODING type is:
YEAR-WEEK-ENCODING ::= SEQUENCE {
year YEAR-ENCODING,
week INTEGER (1..53) -- 6 bits --}


--32.2.12 The ANY-YEAR-WEEK-ENCODING type is:
ANY-YEAR-WEEK-ENCODING ::= SEQUENCE {
year ANY-YEAR-ENCODING,
week INTEGER (1..53)}

-- 32.2.13 The YEAR-WEEK-DAY-ENCODING type is:
YEAR-WEEK-DAY-ENCODING ::= SEQUENCE {
year YEAR-ENCODING,
week INTEGER (1..53), -- 6 bits
day INTEGER (1..7) -- 3 bits -- }

--32.2.14 The ANY-YEAR-WEEK-DAY-ENCODING type is:
ANY-YEAR-WEEK-DAY-ENCODING ::= SEQUENCE {
year ANY-YEAR-ENCODING,
week INTEGER (1..53),
day INTEGER (1..7)}

--32.3 Encoding subtypes with the "Basic=Time" property setting
-- 32.3.1 The HOURS-ENCODING type is:

HOURS-ENCODING ::= SEQUENCE {
as-number INTEGER(0..24) -- 5 bits -- }

--32.3.2 The HOURS-UTC-ENCODING type is:
HOURS-UTC-ENCODING  ::= SEQUENCE {
 as-number INTEGER(0..24) -- 5 bits -- }

--32.3.3 The HOURS-AND-DIFF-ENCODING type is:
HOURS-AND-DIFF-ENCODING ::= SEQUENCE {
local-hours INTEGER (0..24),
time-difference TIME-DIFFERENCE }

TIME-DIFFERENCE ::= SEQUENCE {
sign ENUMERATED { positive, negative },
hours INTEGER (0..15),
minutes INTEGER (1..59) OPTIONAL }

--32.3.4 The MINUTES-ENCODING type is:
MINUTES-ENCODING ::= SEQUENCE {
hours INTEGER (0..24), -- 5 bits
minutes INTEGER (0..59) -- 5 bits -- }

--32.3.5 The MINUTES-UTC-ENCODING type is:
MINUTES-UTC-ENCODING ::= SEQUENCE {
hours INTEGER (0..24), -- 5 bits
minutes INTEGER (0..59) -- 5 bits -- }

-- 32.3.6 The MINUTES-AND-DIFF-ENCODING type is:
MINUTES-AND-DIFF-ENCODING ::= SEQUENCE {
local-time MINUTES-ENCODING,
time-difference TIME-DIFFERENCE }

--32.3.7 The TIME-OF-DAY-ENCODING type is:
TIME-OF-DAY-ENCODING ::= SEQUENCE {
hours INTEGER (0..24), -- 5 bits
minutes INTEGER (0..59), -- 5 bits
seconds INTEGER (0..60) -- 5 bits -- }

--32.3.8 The TIME-OF-DAY-UTC-ENCODING type is:
TIME-OF-DAY-UTC-ENCODING ::= SEQUENCE {
hours INTEGER (0..24), -- 5 bits
minutes INTEGER (0..59), -- 5 bits
seconds INTEGER (0..60) -- 5 bits -- }

--32.3.9 The TIME-OF-DAY-AND-DIFF-ENCODING type is:
TIME-OF-DAY-AND-DIFF-ENCODING ::= SEQUENCE {
local-time TIME-OF-DAY-ENCODING,
time-difference TIME-DIFFERENCE }

-- 32.3.10 The HOURS-AND-FRACTION-ENCODING type is:
HOURS-AND-FRACTION-ENCODING ::= SEQUENCE {
hours INTEGER (0..24), -- 5 bits
fraction INTEGER (0..999, ..., 1000..MAX)
-- 11 bits for up to three digits accuracy -- }


--32.3.11 The HOURS-UTC-AND-FRACTION-ENCODING type is:
HOURS-UTC-AND-FRACTION-ENCODING ::= SEQUENCE {
hours INTEGER (0..24), -- 5 bits
fraction INTEGER (0..999, ..., 1000..MAX)
-- 11 bits for up to three digits accuracy -- }

--32.3.12 The HOURS-AND-DIFF-AND-FRACTION-ENCODING type is:
HOURS-AND-DIFF-AND-FRACTION-ENCODING ::= SEQUENCE {
local-hours INTEGER (0..24), -- 5 bits
fraction INTEGER (0..999, ..., 1000..MAX)
-- 11 bits for up to three digits accuracy -- ,
time-difference TIME-DIFFERENCE }

--32.3.13 The MINUTES-AND-FRACTION-ENCODING type is:
MINUTES-AND-FRACTION-ENCODING ::= SEQUENCE {
hours INTEGER (0..24), -- 5 bits
minutes INTEGER (0..59), -- 5 bits
fraction INTEGER (0..999, ..., 1000..MAX)
-- 11 bits for up to three digits accuracy -- }

--32.3.14 The MINUTES-UTC-AND-FRACTION-ENCODING type is:
MINUTES-UTC-AND-FRACTION-ENCODING ::= SEQUENCE {
hours INTEGER (0..24), -- 5 bits
minutes INTEGER (0..59), -- 5 bits
fraction INTEGER (0..999, ..., 1000..MAX)
-- 11 bits for up to three digits accuracy -- }

--32.3.15 The MINUTES-AND-DIFF-AND-FRACTION-ENCODING type is:
MINUTES-AND-DIFF-AND-FRACTION-ENCODING ::= SEQUENCE {
local-time MINUTES-AND-FRACTION-ENCODING,
time-difference TIME-DIFFERENCE }

--32.3.16 The TIME-OF-DAY-AND-FRACTION-ENCODING type is:
TIME-OF-DAY-AND-FRACTION-ENCODING ::= SEQUENCE {
hours INTEGER (0..24), -- 5 bits
minutes INTEGER (0..59), -- 5 bits
seconds INTEGER (0..60), -- 5 bits --
fraction INTEGER (0..999, ..., 1000..MAX)
-- 11 bits for up to three digits accuracy -- }

--32.3.17 The TIME-OF-DAY-UTC-AND-FRACTION-ENCODING type is:
TIME-OF-DAY-UTC-AND-FRACTION-ENCODING ::= SEQUENCE {
hours INTEGER (0..24), -- 5 bits
minutes INTEGER (0..59), -- 5 bits
seconds INTEGER (0..60), -- 5 bits --
fraction INTEGER (0..999, ..., 1000..MAX)
-- 11 bits for up to three digits accuracy -- }

--32.3.18 The TIME-OF-DAY-AND-DIFF-AND-FRACTION-ENCODING type is:
TIME-OF-DAY-AND-DIFF-AND-FRACTION-ENCODING ::= SEQUENCE {
local-time TIME-OF-DAY-AND-FRACTION-ENCODING,
time-difference TIME-DIFFERENCE }

--32.4 Encoding subtypes with the "Basic=Date-Time" property setting
--32.4.1 The DATE-TIME-ENCODING type is:
DATE-TIME-ENCODING {Date-Type, Time-Type} ::= SEQUENCE {
date Date-Type,
time Time-Type}

--32.5 Encoding subtypes with the "Basic=Interval Interval-type=SE" property setting
--This subclause defines the ASN.1 types referenced in Table 2, column 3 for types where all the abstract values of the
--type have the "Basic=Interval Interval-type=SE" property setting.
--32.5.1 The START-END-DATE-INTERVAL-ENCODING type is:
START-END-DATE-INTERVAL-ENCODING {Date-Type} ::= SEQUENCE {
start Date-Type,
end Date-Type}


--32.5.2 The START-END-TIME-INTERVAL-ENCODING type is:
START-END-TIME-INTERVAL-ENCODING {Time-Type} ::= SEQUENCE {
start Time-Type,
end Time-Type}

--32.5.3 The START-END-DATE-TIME-INTERVAL-ENCODING type is:
START-END-DATE-TIME-INTERVAL-ENCODING {Date-Type, Time-Type} ::=
SEQUENCE {
start DATE-TIME-ENCODING {Date-Type, Time-Type},
end DATE-TIME-ENCODING {Date-Type, Time-Type}}

--32.6.1 The DURATION-INTERVAL-ENCODING type is:
DURATION-INTERVAL-ENCODING ::= SEQUENCE { -- 8 bits for optionality
years INTEGER (0..31, ..., 32..MAX) OPTIONAL,
-- 5 bits for up to 31 years
months INTEGER (0..15, ..., 16..MAX) OPTIONAL,
-- 4 bits for up to 15 months
weeks INTEGER (0..63, ..., 64..MAX) OPTIONAL,
-- 6 bits for up to 63 weeks
days INTEGER (0..31, ..., 32..MAX) OPTIONAL,
-- 5 bits for up to 31 days
hours INTEGER (0..31, ..., 32..MAX) OPTIONAL,
-- 5 bits for up to 31 hours
minutes INTEGER (0..63, ..., 64..MAX) OPTIONAL,
-- 6 bits for up to 63 minutes
seconds INTEGER (0..63, ..., 64..MAX) OPTIONAL,
-- 6 bits for up to 63 seconds
fractional-part SEQUENCE {
number-of-digits INTEGER(1..3, ..., 4..MAX),
-- 3 bits for up to three digits accuracy
fractional-value INTEGER(1..999, ..., 1000..MAX)
-- 11 bits for up to three digits accuracy
} OPTIONAL }

--32.7.1 The START-DATE-DURATION-INTERVAL-ENCODING type is:
START-DATE-DURATION-INTERVAL-ENCODING {Date-Type} ::= SEQUENCE {
start Date-Type,
duration DURATION-INTERVAL-ENCODING}

--32.7.2 The START-TIME-DURATION-INTERVAL-ENCODING type is:
START-TIME-DURATION-INTERVAL-ENCODING {Time-Type} ::= SEQUENCE {
start Time-Type,
duration DURATION-INTERVAL-ENCODING }

--32.7.3 The START-DATE-TIME-DURATION-INTERVAL-ENCODING type is:
START-DATE-TIME-DURATION-INTERVAL-ENCODING {Date-Type, Time-Type} ::=
SEQUENCE {
start DATE-TIME-ENCODING {Date-Type, Time-Type},
duration DURATION-INTERVAL-ENCODING }

--32.7.4 The DURATION-END-DATE-INTERVAL-ENCODING type is:
DURATION-END-DATE-INTERVAL-ENCODING {Date-Type} ::= SEQUENCE {
duration DURATION-INTERVAL-ENCODING,
end Date-Type }

--32.7.5 The DURATION-END-TIME-INTERVAL-ENCODING type is:
DURATION-END-TIME-INTERVAL-ENCODING {Time-Type} ::= SEQUENCE {
duration DURATION-INTERVAL-ENCODING,
end Time-Type }

--32.7.6 The DURATION-END-DATE-TIME-INTERVAL-ENCODING type is:
DURATION-END-DATE-TIME-INTERVAL-ENCODING {Date-Type, Time-Type} ::= SEQUENCE {
duration DURATION-INTERVAL-ENCODING,
end DATE-TIME-ENCODING {Date-Type, Time-Type}}

--32.8 Encoding subtypes with the "Basic=Rec-Interval Interval-type=SE" property setting
-- 32.8.1 The REC-START-END-DATE-INTERVAL-ENCODING type is:
REC-START-END-DATE-INTERVAL-ENCODING {Date-Type} ::= SEQUENCE {
recurrence INTEGER OPTIONAL,
start Date-Type,
end Date-Type}

--32.8.2 The REC-START-END-TIME-INTERVAL-ENCODING type is:
REC-START-END-TIME-INTERVAL-ENCODING {Time-Type} ::= SEQUENCE {
recurrence INTEGER OPTIONAL,
start Time-Type,
end Time-Type}

--32.8.3 The REC-START-END-DATE-TIME-INTERVAL-ENCODING type is:
REC-START-END-DATE-TIME-INTERVAL-ENCODING {Date-Type, Time-Type} ::=
SEQUENCE {
recurrence INTEGER OPTIONAL,
start DATE-TIME-ENCODING {Date-Type, Time-Type},
end DATE-TIME-ENCODING {Date-Type, Time-Type}}

--32.9 Encoding subtypes with the "Basic=Rec-Interval Interval-type=D" property setting
--32.9.1 The REC-DURATION-INTERVAL-ENCODING type is:
REC-DURATION-INTERVAL-ENCODING ::= SEQUENCE {
recurrence INTEGER OPTIONAL,
duration DURATION-INTERVAL-ENCODING}

--32.10 Encoding subtypes with the "Basic=Rec-Interval Interval-type=SD" or
--32.10.1 The REC-START-DATE-DURATION-INTERVAL-ENCODING type is:
REC-START-DATE-DURATION-INTERVAL-ENCODING {Date-Type} ::= SEQUENCE {
recurrence INTEGER OPTIONAL,
start Date-Type,
duration DURATION-INTERVAL-ENCODING}

--32.10.2 The REC-START-TIME-DURATION-INTERVAL-ENCODING type is:
REC-START-TIME-DURATION-INTERVAL-ENCODING {Time-Type} ::= SEQUENCE {
recurrence INTEGER OPTIONAL,
start Time-Type,
duration DURATION-INTERVAL-ENCODING }

--32.10.3 The REC-START-DATE-TIME-DURATION-INTERVAL-ENCODING type is:
REC-START-DATE-TIME-DURATION-INTERVAL-ENCODING {Date-Type, Time-Type} ::= SEQUENCE
{
recurrence INTEGER OPTIONAL,
start DATE-TIME-ENCODING {Date-Type, Time-Type},
duration DURATION-INTERVAL-ENCODING }

--32.10.4 The REC-DURATION-END-DATE-INTERVAL-ENCODING type is:
REC-DURATION-END-DATE-INTERVAL-ENCODING {Date-Type} ::= SEQUENCE {
recurrence INTEGER OPTIONAL,
duration DURATION-INTERVAL-ENCODING,
end Date-Type }

--32.10.5 The REC-DURATION-END-TIME-INTERVAL-ENCODING type is:
REC-DURATION-END-TIME-INTERVAL-ENCODING {Time-Type} ::= SEQUENCE {
recurrence INTEGER OPTIONAL,
duration DURATION-INTERVAL-ENCODING,
end Time-Type }

--32.10.6 The REC-DURATION-END-DATE-TIME-INTERVAL-ENCODING type is:
REC-DURATION-END-DATE-TIME-INTERVAL-ENCODING {Date-Type, Time-Type} ::= SEQUENCE {
recurrence INTEGER OPTIONAL,
duration DURATION-INTERVAL-ENCODING,
end DATE-TIME-ENCODING {Date-Type, Time-Type}}

--32.11.5 The encoding of the abstract value shall be the encoding of the MIXED-ENCODING type:
MIXED-ENCODING ::= CHOICE {
row-1 CENTURY-ENCODING,
row-2 ANY-CENTURY-ENCODING,
row-3 YEAR-ENCODING,
row-4 ANY-YEAR-ENCODING,
row-5 YEAR-MONTH-ENCODING,
row-6 ANY-YEAR-MONTH-ENCODING,
row-7 DATE-ENCODING,
row-8 ANY-DATE-ENCODING,
row-9 YEAR-DAY-ENCODING,
row-10 ANY-YEAR-DAY-ENCODING,
row-11 YEAR-WEEK-ENCODING,
row-12 ANY-YEAR-WEEK-ENCODING,
row-13 YEAR-WEEK-DAY-ENCODING,
row-14 ANY-YEAR-WEEK-DAY-ENCODING,
row-15 HOURS-ENCODING,
row-16 HOURS-UTC-ENCODING,
row-17 HOURS-AND-DIFF-ENCODING,
row-18 MINUTES-ENCODING,
row-19 MINUTES-UTC-ENCODING,
row-20 MINUTES-AND-DIFF-ENCODING,
row-21 TIME-OF-DAY-ENCODING,
row-22 TIME-OF-DAY-UTC-ENCODING,
row-23 TIME-OF-DAY-AND-DIFF-ENCODING,
row-24 FRACTIONAL-TIME{HOURS-AND-FRACTION-ENCODING},
row-25 FRACTIONAL-TIME{HOURS-UTC-AND-FRACTION-ENCODING},
row-26 FRACTIONAL-TIME{HOURS-AND-DIFF-AND-FRACTION-ENCODING},
row-27 FRACTIONAL-TIME{MINUTES-AND-FRACTION-ENCODING},
row-28 FRACTIONAL-TIME{MINUTES-UTC-AND-FRACTION-ENCODING},
row-29 FRACTIONAL-TIME{MINUTES-AND-DIFF-AND-FRACTION-ENCODING},
row-30 FRACTIONAL-TIME{TIME-OF-DAY-AND-FRACTION-ENCODING},
row-31 FRACTIONAL-TIME{TIME-OF-DAY-UTC-AND-FRACTION-ENCODING},
row-32 FRACTIONAL-TIME{TIME-OF-DAY-AND-DIFF-AND-FRACTION-ENCODING},
row-33 DATE-TIME-ENCODING {DATE-TYPE, TIME-TYPE},
row-34 START-END-DATE-INTERVAL-ENCODING {DATE-TYPE},
row-35 START-END-TIME-INTERVAL-ENCODING {TIME-TYPE},
row-36 START-END-DATE-TIME-INTERVAL-ENCODING {DATE-TYPE, TIME-TYPE},
row-37 DURATION-INTERVAL-ENCODING,
row-38 START-DATE-DURATION-INTERVAL-ENCODING {DATE-TYPE},
row-39 START-TIME-DURATION-INTERVAL-ENCODING {TIME-TYPE},
row-40 START-DATE-TIME-DURATION-INTERVAL-ENCODING {DATE-TYPE, TIME-TYPE},
row-41 DURATION-END-DATE-INTERVAL-ENCODING {DATE-TYPE},
row-42 DURATION-END-TIME-INTERVAL-ENCODING {TIME-TYPE},
row-43 DURATION-END-DATE-TIME-INTERVAL-ENCODING {DATE-TYPE, TIME-TYPE},
row-44 REC-START-END-DATE-INTERVAL-ENCODING {DATE-TYPE},
row-45 REC-START-END-TIME-INTERVAL-ENCODING {TIME-TYPE},
row-46 REC-START-END-DATE-TIME-INTERVAL-ENCODING {DATE-TYPE, TIME-TYPE},
row-47 REC-DURATION-INTERVAL-ENCODING,
row-48 REC-START-DATE-DURATION-INTERVAL-ENCODING {DATE-TYPE},
row-49 REC-START-TIME-DURATION-INTERVAL-ENCODING {TIME-TYPE},
row-50 REC-START-DATE-TIME-DURATION-INTERVAL-ENCODING {DATE-TYPE, TIME-TYPE},
row-51 REC-DURATION-END-DATE-INTERVAL-ENCODING {DATE-TYPE},
row-52 REC-DURATION-END-TIME-INTERVAL-ENCODING {TIME-TYPE},
row-53 REC-DURATION-END-DATE-TIME-INTERVAL-ENCODING {DATE-TYPE, TIME-TYPE} }

--32.11.6 FRACTIONAL-TIME is defined as follows:
FRACTIONAL-TIME{Time-Type} ::= SEQUENCE {
number-of-digits INTEGER (1..MAX),
time-value Time-Type}

--32.11.7 The DATE-TYPE is:
DATE-TYPE ::= CHOICE {
date-C-Basic CENTURY-ENCODING,
date-C-L ANY-CENTURY-ENCODING,
date-Y-Basic YEAR-ENCODING,
date-Y-L ANY-YEAR-ENCODING,
date-YM-Basic YEAR-MONTH-ENCODING,
date-YM-L ANY-YEAR-MONTH-ENCODING,
date-YMD-Basic DATE-ENCODING,
date-YMD-L ANY-DATE-ENCODING,
date-YD-Basic YEAR-DAY-ENCODING,
date-YD-L ANY-YEAR-DAY-ENCODING,
date-YW-Basic YEAR-WEEK-ENCODING,
date-YW-L ANY-YEAR-WEEK-ENCODING,
date-YWD-Basic YEAR-WEEK-DAY-ENCODING,
date-YWD-L ANY-YEAR-WEEK-DAY-ENCODING }

--32.11.8 The TIME-TYPE is:
TIME-TYPE ::= SEQUENCE {
number-of-digits INTEGER (1..MAX) OPTIONAL,
time-type CHOICE {
time-H-L HOURS-ENCODING,
time-H-Z  HOURS-UTC-ENCODING,
time-H-LD  HOURS-AND-DIFF-ENCODING,
time-HM-L  MINUTES-ENCODING,
time-HM-Z MINUTES-UTC-ENCODING,
time-HM-LD MINUTES-AND-DIFF-ENCODING,
time-HMS-L TIME-OF-DAY-ENCODING,
time-HMS-Z TIME-OF-DAY-UTC-ENCODING,
time-HMS-LD TIME-OF-DAY-AND-DIFF-ENCODING,
time-HFn-L HOURS-AND-FRACTION-ENCODING,
time-HFn-Z HOURS-UTC-AND-FRACTION-ENCODING,
time-HFn-LD HOURS-AND-DIFF-AND-FRACTION-ENCODING,
time-HMFn-L MINUTES-AND-FRACTION-ENCODING,
time-HMFn-Z MINUTES-UTC-AND-FRACTION-ENCODING,
time-HMFn-LD MINUTES-AND-DIFF-AND-FRACTION-ENCODING,
time-HMFSn-L TIME-OF-DAY-AND-FRACTION-ENCODING,
time-HMFSn-Z TIME-OF-DAY-UTC-AND-FRACTION-ENCODING,
time-HMFSn-LD TIME-OF-DAY-AND-DIFF-AND-FRACTION-ENCODING } }


END
